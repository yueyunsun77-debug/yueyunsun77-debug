package IndicatorRequirementModel {
    doc /* 每个独立指标与JSON IND编号一一对应，待定数值不形式化为假定约束。 */
    requirement <'IND-001'> I001 {
        doc /* 空气输送功能状态；分配到加热使能判断；空气输送功能必须处于开启状态 */
    }
    requirement <'IND-002'> I002 {
        doc /* 目标温度与室内温度关系；分配到加热使能判断；目标温度高于室内温度 */
    }
    requirement <'IND-003'> I003 {
        doc /* 车辆高压状态；分配到加热使能判断；车辆处于高压状态 */
    }
    requirement <'IND-004'> I004 {
        doc /* 整车故障状态；分配到故障状态与加热许可判断；整车无故障 */
    }
    requirement <'IND-005'> I005 {
        doc /* SOC使能阈值；分配到电量与加热许可判断；SOC > 10% */
    }
    requirement <'IND-006'> I006 {
        doc /* 电加热通断控制；分配到电加热通断控制；满足全部使能条件后，CCU按请求控制电加热通断闭合/断开 */
    }
    requirement <'IND-007'> I007 {
        doc /* 电加热过温断开阈值；分配到电加热过温保护；电加热温度 ≥ XXX ℃ 时断开继电器；具体阈值待标定 */
    }
    requirement <'IND-008'> I008 {
        doc /* 电加热重新允许闭合温度；分配到电加热恢复许可控制；电加热温度 ≤ XXX ℃ 时才允许恢复电加热输出；具体阈值待标定 */
    }
    requirement <'IND-009'> I009 {
        doc /* 电加热状态反馈内容；分配到加热状态反馈；电加热通断状态、电加热当前温度、电加热工作状态、实际功率、最大工作功率发送至总线 */
    }
    requirement <'IND-010'> I010 {
        doc /* 电加热控制响应时间；分配到电加热通断控制；TBD（所给规范未明确具体时限） */
    }
    requirement <'IND-011'> I011 {
        doc /* 低温边界显示；分配到目标温度边界判定；设定温度 < 16 ℃ 时定义为 LO */
    }
    requirement <'IND-012'> I012 {
        doc /* 高温边界显示；分配到目标温度边界判定；设定温度 > 30 ℃ 时定义为 HI */
    }
    requirement <'IND-013'> I013 {
        doc /* 单次温度调节步长；分配到目标温度更新；每次温度增加/减小 0.5 ℃ */
    }
    requirement <'IND-014'> I014 {
        doc /* 自动调节输入信息；分配到温度与环境信息采集；室内温度、室外温度、日照负荷信息、供热入口温度 */
    }
    requirement <'IND-015'> I015 {
        doc /* 自动调节对象；分配到自动温控协调；空气输送能力、送风温度调节、送风模式调节、循环方式调节、制冷执行能力（转速接口）；根据系统配置控制电加热功率 */
    }
    requirement <'IND-016'> I016 {
        doc /* 自动模式状态反馈；分配到自动模式状态反馈；CCU反馈自动模式状态给IVI；接口信号包括 CCU_AUTO_Status */
    }
    requirement <'IND-017'> I017 {
        doc /* 空调状态反馈内容；分配到空调状态反馈；空气输送等级、温度档位、AC状态、循环状态、吹风模式、AUTO状态 */
    }
    requirement <'IND-018'> I018 {
        doc /* 温度调节后的模式状态；分配到自动模式保持与切换；AUTO状态下调节温度不退出AUTO，仅更新目标温度并继续自动控制 */
    }
    requirement <'IND-019'> I019 {
        doc /* 目标温度控制偏差；分配到座舱温度闭环调节；TBD（原表未给出控制偏差数值） */
    }
    requirement <'IND-020'> I020 {
        doc /* 目标温度稳定时间；分配到座舱温度闭环调节；TBD（原表未给出稳定时间数值） */
    }
    requirement <'IND-021'> I021 {
        doc /* 前除霜/除雾请求通道；分配到风窗请求接收；IVI通过CAN向CCU发送前除霜/前除雾请求 */
    }
    requirement <'IND-022'> I022 {
        doc /* 初始出风口位置；分配到送风模式调节；进入前除霜/除雾状态后，出风口切换至对应除霜/除雾位置 */
    }
    requirement <'IND-023'> I023 {
        doc /* 初始空气输送功能风量；分配到空气输送与风量调节；最大风量 */
    }
    requirement <'IND-024'> I024 {
        doc /* 外循环开度；分配到循环方式调节；90%（原规范标注待定） */
    }
    requirement <'IND-025'> I025 {
        doc /* 除湿时制冷执行能力（转速接口）；分配到制冷能力调节；最低转速 1000 r/min（规范描述为除湿用途；相关转速仍需结合标定确认） */
    }
    requirement <'IND-026'> I026 {
        doc /* 进入模式后的温度设定；分配到目标温度保持；温度保持不变；用户操作温度按键时按规范更新当前设定 */
    }
    requirement <'IND-027'> I027 {
        doc /* 前除霜/除雾反馈内容；分配到风窗与空调状态反馈；空气输送等级、温度状态、AC状态、循环状态、前除霜/除雾状态反馈给IVI */
    }
    requirement <'IND-028'> I028 {
        doc /* 热管理控制优先级；分配到热管理能力仲裁；前除霜模式 > 电池包降温（达到阈值）> 乘员舱制冷 > 电池包降温（未达到阈值） */
    }
    requirement <'IND-029'> I029 {
        doc /* SOC低于10%时的制冷执行功能许可；分配到低电量制冷许可判断；前除霜关闭时不允许制冷执行功能输出功率；前除霜开启时允许开启制冷执行功能 */
    }
    requirement <'IND-030'> I030 {
        doc /* 后风窗除霜/除雾参数；分配到后风窗服务待确认；TBD（所给两份PDF未找到完整后风窗控制逻辑及具体指标） */
    }
    requirement <'IND-031'> I031 {
        doc /* 风窗请求响应时间；分配到风窗除霜除雾控制；TBD（原表未给出请求响应时限） */
    }
    requirement <'IND-032'> I032 {
        doc /* 风窗除霜除雾效果达成时间；分配到风窗除霜除雾控制；TBD（原表未给出效果时限及验收阈值） */
    }
    requirement <'IND-033'> I033 {
        doc /* 室内温度信息检测周期；分配到温度与环境信息采集；CCU初始化后，每隔50 ms检测对应温度；检测周期不是CAN发送周期。 */
    }
    requirement <'IND-034'> I034 {
        doc /* 电加热温度信息检测周期；分配到电加热温度信息采集；CCU初始化后，每隔50 ms检测对应温度；检测周期不是CAN发送周期。 */
    }
    requirement <'IND-035'> I035 {
        doc /* AC操作后的制冷转速请求；分配到AUTO下AC操作处理；AUTO状态下操作AC按键，关闭制冷请求且转速请求为0；其余指定功能继续自动控制。 */
    }
    requirement <'IND-036'> I036 {
        doc /* AC操作后的AUTO状态反馈；分配到AUTO下AC操作处理；AUTO状态下操作AC按键时，反馈AUTO状态为Close；风量、温度、模式与循环仍保持自动操作。 */
    }
    requirement <'IND-037'> I037 {
        doc /* 发动机优先运行负载；分配到高效发电运行调节；发动机启动后优先维持50%以上负载；运行偏好不作为全工况硬下限。 */
    }
    requirement <'IND-038'> I038 {
        doc /* 静置预冷持续时间；分配到静置预冷计时；车辆静置，驾驶员启动空调，座舱预冷持续2分钟。 */
    }
    requirement <'IND-039'> I039 {
        doc /* 第二阶段匀速行驶速度；分配到匀速行驶工况控制；静置阶段之后以45 km/h匀速行驶。 */
    }
    requirement <'IND-040'> I040 {
        doc /* 第二阶段匀速行驶持续时间；分配到匀速行驶工况控制；第二阶段匀速行驶持续20分钟。 */
    }
    requirement <'IND-041'> I041 {
        doc /* 场景二电池主动冷却触发温度；分配到电池主动冷却触发判断；电芯温度达到或超过35℃时引入座舱空调主动冷却。不是安全温度上限，退出策略未提供。 */
    }
}
